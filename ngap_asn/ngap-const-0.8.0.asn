-- **************************************************************
--
-- Constant definitions
--
-- **************************************************************

NGAP-Constants { 
itu-t (0) identified-organization (4) etsi (0) mobileDomain (0) 
ngran-Access (22) modules (3) ngap (1) version1 (1) ngap-Constants (4) } 

DEFINITIONS AUTOMATIC TAGS ::= 

BEGIN

-- **************************************************************
--
-- IE parameter types from other modules.
--
-- **************************************************************

IMPORTS

	ProcedureCode,
	ProtocolIE-ID
FROM NGAP-CommonDataTypes;


-- **************************************************************
--
-- Elementary Procedures
--
-- **************************************************************

id-AMFConfigurationUpdate					ProcedureCode ::= 0
id-AMFStatusIndication						ProcedureCode ::= 1
id-CellTrafficTrace							ProcedureCode ::= 2
id-DeactivateTrace							ProcedureCode ::= 3
id-DownlinkNASTransport						ProcedureCode ::= 4
id-DownlinkNonUEAssociatedNRPPaTransport	ProcedureCode ::= 5
id-DownlinkRANConfigurationTransfer			ProcedureCode ::= 6
id-DownlinkRANStatusTransfer				ProcedureCode ::= 7
id-DownlinkUEAssociatedNRPPaTransport		ProcedureCode ::= 8
id-ErrorIndication							ProcedureCode ::= 9
id-HandoverCancel							ProcedureCode ::= 10
id-HandoverNotification						ProcedureCode ::= 11
id-HandoverPreparation						ProcedureCode ::= 12
id-HandoverResourceAllocation				ProcedureCode ::= 13
id-InitialContextSetup						ProcedureCode ::= 14
id-InitialUEMessage							ProcedureCode ::= 15
id-LocationReportingControl					ProcedureCode ::= 16
id-LocationReportingFailureIndication		ProcedureCode ::= 17
id-LocationReport							ProcedureCode ::= 18
id-NASNonDeliveryIndication					ProcedureCode ::= 19
id-NGReset									ProcedureCode ::= 20
id-NGSetup									ProcedureCode ::= 21
id-Paging									ProcedureCode ::= 22
id-PathSwitchRequest						ProcedureCode ::= 23
id-PDUSessionResourceModify					ProcedureCode ::= 24
id-PDUSessionResourceModifyIndication		ProcedureCode ::= 25
id-PDUSessionResourceRelease				ProcedureCode ::= 26
id-PDUSessionResourceSetup					ProcedureCode ::= 27
id-PDUSessionResourceNotify					ProcedureCode ::= 28
id-PrivateMessage							ProcedureCode ::= 29
id-PWSCancel								ProcedureCode ::= 30
id-PWSFailureIndication						ProcedureCode ::= 31
id-PWSRestartIndication						ProcedureCode ::= 32
id-RANConfigurationUpdate					ProcedureCode ::= 33
id-RerouteNASRequest						ProcedureCode ::= 34
id-TraceFailureIndication					ProcedureCode ::= 35
id-TraceStart								ProcedureCode ::= 36
id-UECapabilityInfoIndication				ProcedureCode ::= 37
id-UEContextModification					ProcedureCode ::= 38
id-UEContextRelease							ProcedureCode ::= 39
id-UEContextReleaseRequest					ProcedureCode ::= 40
id-UERadioCapabilityCheck					ProcedureCode ::= 41
id-UETNLABindingRelease						ProcedureCode ::= 42
id-UplinkNASTransport						ProcedureCode ::= 43
id-UplinkNonUEAssociatedNRPPaTransport		ProcedureCode ::= 44
id-UplinkRANConfigurationTransfer			ProcedureCode ::= 45
id-UplinkRANStatusTransfer					ProcedureCode ::= 46
id-UplinkUEAssociatedNRPPaTransport			ProcedureCode ::= 47
id-WriteReplaceWarning						ProcedureCode ::= 48

-- **************************************************************
--
-- Extension constants
--
-- **************************************************************

maxPrivateIEs							INTEGER ::= 65535
maxProtocolExtensions					INTEGER ::= 65535
maxProtocolIEs							INTEGER ::= 65535

-- **************************************************************
--
-- Lists
--
-- **************************************************************

	maxnoofAllowedAreas					INTEGER ::= 16
	maxnoofAllowedS-NSSAIs				INTEGER ::= 8
	maxnoofBPLMNs						INTEGER ::= 12
	maxnoofCellIDforWarning				INTEGER ::= 65535
	maxnoofCellinEAI					INTEGER ::= 65535
	maxnoofCellinTAI					INTEGER ::= 65535
	maxnoofCellsingNB					INTEGER ::= 16384
	maxnoofCellsinngeNB					INTEGER ::= 256
	maxnoofDRBs							INTEGER ::= 32
	maxnoofEmergencyAreaID				INTEGER ::= 65535
	maxnoofEAIforRestart				INTEGER ::= 256
	maxnoofEPLMNs						INTEGER ::= 15
	maxnoofEPLMNsPlusOne				INTEGER ::= 16
	maxnoofE-RABs						INTEGER ::= 256
	maxnoofErrors						INTEGER ::= 256
	maxnoofForbTACs						INTEGER ::= 4096
	maxnoofMultiConnectivities			INTEGER ::= 8
	maxnoofNGConnectionsToReset			INTEGER ::= 8192
	maxnoofPDUSessions					INTEGER ::= 256
	maxnoofPLMNs						INTEGER ::= 12
	maxnoofQosFlows						INTEGER ::= 64
	maxnoofRecommendedCells				INTEGER ::= 16
	maxnoofAoI							INTEGER ::= 64
	maxnoofServedGUAMIs					INTEGER ::= 256
	maxnoofSliceItems					INTEGER ::= 1024
	maxnoofTACs							INTEGER ::= 256
	maxnoofTAIs							INTEGER ::= 16
	maxnoofTAIforRestart				INTEGER ::= 2048
	maxnoofTAIforWarning				INTEGER ::= 65535
	maxnoofTNLAssociations				INTEGER ::= 32
	maxnoofXnExtTLAs					INTEGER ::= 2
	maxnoofXnGTP-TLAs					INTEGER ::= 16
	maxnoofXnTLAs						INTEGER ::= 16

-- **************************************************************
--
-- IEs
--
-- **************************************************************

	id-AllowedNSSAI											ProtocolIE-ID ::= 0
	id-AMFName 												ProtocolIE-ID ::= 1
	id-AMFSetID												ProtocolIE-ID ::= 2
	id-AMF-TNLAssociationFailedToSetupList					ProtocolIE-ID ::= 3
	id-AMF-TNLAssociationSetupItem							ProtocolIE-ID ::= 4
	id-AMF-TNLAssociationSetupList							ProtocolIE-ID ::= 5
	id-AMF-TNLAssociationToAddItem							ProtocolIE-ID ::= 6
	id-AMF-TNLAssociationToAddList							ProtocolIE-ID ::= 7
	id-AMF-TNLAssociationToRemoveItem						ProtocolIE-ID ::= 8
	id-AMF-TNLAssociationToRemoveList						ProtocolIE-ID ::= 9
	id-AMF-TNLAssociationToUpdateItem						ProtocolIE-ID ::= 10
	id-AMF-TNLAssociationToUpdateList						ProtocolIE-ID ::= 11
	id-AMF-UE-NGAP-ID										ProtocolIE-ID ::= 12
	id-AssistanceDataForPaging								ProtocolIE-ID ::= 13
	id-BroadcastCancelledAreaList							ProtocolIE-ID ::= 14
	id-BroadcastCompletedAreaList							ProtocolIE-ID ::= 15
	id-CancelAllWarningMessages								ProtocolIE-ID ::= 16
	id-Cause												ProtocolIE-ID ::= 17
	id-CellIDListForRestart									ProtocolIE-ID ::= 18
	id-ConcurrentWarningMessageInd							ProtocolIE-ID ::= 19
	id-CriticalityDiagnostics								ProtocolIE-ID ::= 20
	id-DataCodingScheme										ProtocolIE-ID ::= 21
	id-DefaultPagingDRX										ProtocolIE-ID ::= 22
	id-DirectForwardingPathAvailability						ProtocolIE-ID ::= 23
	id-EmergencyAreaIDListForRestart						ProtocolIE-ID ::= 24
	id-EmergencyFallbackIndicator							ProtocolIE-ID ::= 25
	id-EUTRA-CGI											ProtocolIE-ID ::= 26
	id-FiveG-S-TMSI											ProtocolIE-ID ::= 27
	id-GlobalRANNodeID										ProtocolIE-ID ::= 28
	id-GUAMI												ProtocolIE-ID ::= 29
	id-HandoverType											ProtocolIE-ID ::= 30
	id-IMSVoiceSupportIndicator								ProtocolIE-ID ::= 31
	id-IndexToRFSP											ProtocolIE-ID ::= 32
	id-InfoOnRecommendedCellsAndRANNodesForPaging 			ProtocolIE-ID ::= 33
	id-KamfChangeInd										ProtocolIE-ID ::= 34
	id-LocationReportingRequestType							ProtocolIE-ID ::= 35
	id-MaskedIMEISV											ProtocolIE-ID ::= 36
	id-MessageIdentifier									ProtocolIE-ID ::= 37
	id-MobilityRestrictionList								ProtocolIE-ID ::= 38
	id-NASC													ProtocolIE-ID ::= 39
	id-NAS-PDU												ProtocolIE-ID ::= 40
	id-NewAMF-UE-NGAP-ID									ProtocolIE-ID ::= 41
	id-NGAP-Message											ProtocolIE-ID ::= 42
	id-NGRAN-CGI											ProtocolIE-ID ::= 43
	id-NGRANTraceID											ProtocolIE-ID ::= 44
	id-NR-CGI												ProtocolIE-ID ::= 45
	id-NRPPa-PDU											ProtocolIE-ID ::= 46
	id-NumberOfBroadcastsRequested							ProtocolIE-ID ::= 47
	id-OldAMF												ProtocolIE-ID ::= 48
	id-PagingDRX											ProtocolIE-ID ::= 49
	id-PagingOrigin											ProtocolIE-ID ::= 50
	id-PagingPriority										ProtocolIE-ID ::= 51
	id-PDUSessionResourceAdmittedItem						ProtocolIE-ID ::= 52
	id-PDUSessionResourceAdmittedList						ProtocolIE-ID ::= 53
	id-PDUSessionResourceFailedToModifyListModRes			ProtocolIE-ID ::= 54
	id-PDUSessionResourceFailedToSetupList					ProtocolIE-ID ::= 55
	id-PDUSessionResourceItemHORqd							ProtocolIE-ID ::= 56
	id-PDUSessionResourceListHORqd							ProtocolIE-ID ::= 57
	id-PDUSessionResourceModifyItemModCfm					ProtocolIE-ID ::= 58
	id-PDUSessionResourceModifyItemModInd					ProtocolIE-ID ::= 59
	id-PDUSessionResourceModifyItemModReq					ProtocolIE-ID ::= 60
	id-PDUSessionResourceModifyItemModRes					ProtocolIE-ID ::= 61
	id-PDUSessionResourceModifyListModCfm					ProtocolIE-ID ::= 62
	id-PDUSessionResourceModifyListModInd					ProtocolIE-ID ::= 63
	id-PDUSessionResourceModifyListModReq					ProtocolIE-ID ::= 64
	id-PDUSessionResourceModifyListModRes					ProtocolIE-ID ::= 65
	id-PDUSessionResourceNotifyItem							ProtocolIE-ID ::= 66
	id-PDUSessionResourceNotifyList							ProtocolIE-ID ::= 67
	id-PDUSessionResourceReleasedList						ProtocolIE-ID ::= 68
	id-PDUSessionResourceSetupItemCxtReq					ProtocolIE-ID ::= 69
	id-PDUSessionResourceSetupItemCxtRes					ProtocolIE-ID ::= 70
	id-PDUSessionResourceSetupItemHOReq						ProtocolIE-ID ::= 71
	id-PDUSessionResourceSetupItemSUReq						ProtocolIE-ID ::= 72
	id-PDUSessionResourceSetupItemSURes						ProtocolIE-ID ::= 73
	id-PDUSessionResourceSetupListCxtReq					ProtocolIE-ID ::= 74
	id-PDUSessionResourceSetupListCxtRes					ProtocolIE-ID ::= 75
	id-PDUSessionResourceSetupListHOReq						ProtocolIE-ID ::= 76
	id-PDUSessionResourceSetupListSUReq						ProtocolIE-ID ::= 77
	id-PDUSessionResourceSetupListSURes						ProtocolIE-ID ::= 78
	id-PDUSessionResourceSubjectToForwardingItem			ProtocolIE-ID ::= 79
	id-PDUSessionResourceSubjectToForwardingList			ProtocolIE-ID ::= 80
	id-PDUSessionResourceToBeSwitchedDLItem					ProtocolIE-ID ::= 81
	id-PDUSessionResourceToBeSwitchedDLList					ProtocolIE-ID ::= 82
	id-PDUSessionResourceToBeSwitchedULItem					ProtocolIE-ID ::= 83
	id-PDUSessionResourceToBeSwitchedULList					ProtocolIE-ID ::= 84
	id-PDUSessionResourceToReleaseList						ProtocolIE-ID ::= 85
	id-PLMNSupportList										ProtocolIE-ID ::= 86
	id-PWSFailedCellIDList									ProtocolIE-ID ::= 87
	id-RANNodeName											ProtocolIE-ID ::= 88
	id-RANPagingPriority									ProtocolIE-ID ::= 89
	id-RANStatusTransfer-TransparentContainer				ProtocolIE-ID ::= 90
	id-RAN-UE-NGAP-ID										ProtocolIE-ID ::= 91
	id-RelativeAMFCapacity									ProtocolIE-ID ::= 92
	id-RepetitionPeriod										ProtocolIE-ID ::= 93
	id-ResetType											ProtocolIE-ID ::= 94
	id-RoutingID											ProtocolIE-ID ::= 95
	id-RRCEstablishmentCause								ProtocolIE-ID ::= 96
	id-RRCInactiveAssistanceInformation						ProtocolIE-ID ::= 97
	id-SecurityContext										ProtocolIE-ID ::= 98
	id-SecurityKey											ProtocolIE-ID ::= 99
	id-SerialNumber											ProtocolIE-ID ::= 100
	id-ServedGUAMIList										ProtocolIE-ID ::= 101
	id-SliceSupportList										ProtocolIE-ID ::= 102
	id-SONConfigurationTransferDL							ProtocolIE-ID ::= 103
	id-SONConfigurationTransferUL							ProtocolIE-ID ::= 104
	id-SourceAMF-UE-NGAP-ID									ProtocolIE-ID ::= 105
	id-SourceToTarget-TransparentContainer					ProtocolIE-ID ::= 106
	id-SupportedTAList										ProtocolIE-ID ::= 107
	id-TAI													ProtocolIE-ID ::= 108
	id-TAIItem												ProtocolIE-ID ::= 109
	id-TAIList												ProtocolIE-ID ::= 110
	id-TAIListForRestart									ProtocolIE-ID ::= 111
	id-TargetID												ProtocolIE-ID ::= 112
	id-TargetToSource-TransparentContainer					ProtocolIE-ID ::= 113
	id-TimeStamp											ProtocolIE-ID ::= 114
	id-TimeToWait											ProtocolIE-ID ::= 115
	id-TraceActivation										ProtocolIE-ID ::= 116
	id-TraceCollectionEntityIPAddress						ProtocolIE-ID ::= 117
	id-UEAggregateMaximumBitRate							ProtocolIE-ID ::= 118
	id-UE-associatedLogicalNG-ConnectionItem				ProtocolIE-ID ::= 119
	id-UE-associatedLogicalNG-ConnectionListResAck			ProtocolIE-ID ::= 120
	id-UEContextRequest										ProtocolIE-ID ::= 121
	id-UEIdentityIndexValue									ProtocolIE-ID ::= 122
	id-UE-NGAP-IDs											ProtocolIE-ID ::= 123
	id-UEPagingIdentity										ProtocolIE-ID ::= 124
	id-UEPresenceInAreaOfInterestList						ProtocolIE-ID ::= 125
	id-UERadioCapability									ProtocolIE-ID ::= 126
	id-UERadioCapabilityForPaging							ProtocolIE-ID ::= 127
	id-UESecurityCapabilities								ProtocolIE-ID ::= 128
	id-UnavailableGUAMIList									ProtocolIE-ID ::= 129
	id-UserLocationInformation								ProtocolIE-ID ::= 130
	id-WarningAreaList										ProtocolIE-ID ::= 131
	id-WarningMessageContents								ProtocolIE-ID ::= 132
	id-WarningSecurityInfo									ProtocolIE-ID ::= 133
	id-WarningType											ProtocolIE-ID ::= 134
END
